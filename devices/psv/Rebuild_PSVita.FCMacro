"""Rebuild the PCH-1000 Wi-Fi OLED study without overwriting its delivered models."""
from pathlib import Path
import sys,importlib
root=Path(__file__).resolve().parent;repo=root.parents[1]
if str(repo/'tools') not in sys.path:sys.path.insert(0,str(repo/'tools'))
from cadlib import core,geometry,handheld_refinement,fidelity_psv,part_numbers,psv,deliver
for module in [geometry,core,handheld_refinement,fidelity_psv,part_numbers,psv,deliver]:importlib.reload(module)
model=core.Study(repo,'psv');model.out=root/'output/rebuilt'
for folder in ['iterations','reports','previews','drawings']:(model.out/folder).mkdir(parents=True,exist_ok=True)
for stage in range(1,17):psv.STAGES[stage](model)
deliver.finalize(model)
