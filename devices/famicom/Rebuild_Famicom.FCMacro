"""Rebuild the original HVC-001 Famicom study without overwriting its delivered models."""
from pathlib import Path
import sys,importlib
root=Path(__file__).resolve().parent;repo=root.parents[1]
if str(repo/'tools') not in sys.path:sys.path.insert(0,str(repo/'tools'))
from cadlib import core,geometry,fidelity_famicom,famicom,deliver
for module in [geometry,core,fidelity_famicom,famicom,deliver]:importlib.reload(module)
model=core.Study(repo,'famicom');model.out=root/'output/rebuilt'
for folder in ['iterations','reports','previews','drawings']:(model.out/folder).mkdir(parents=True,exist_ok=True)
for stage in sorted(famicom.STAGES):famicom.STAGES[stage](model)
deliver.finalize(model)
