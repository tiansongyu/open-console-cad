"""Rebuild the current original SHVC001 study from source."""
from pathlib import Path
import sys,importlib
root=Path(__file__).resolve().parent;repo=root.parents[1]
sys.path.insert(0,str(repo/'tools'))
from cadlib import core,sfc,deliver,fidelity_sfc
importlib.reload(fidelity_sfc)
importlib.reload(sfc)
model=core.Study(repo,'sfc');model.out=root/'output/rebuilt'
for folder in ['iterations','reports','previews','drawings']:(model.out/folder).mkdir(parents=True,exist_ok=True)
for i in sorted(sfc.STAGES):sfc.STAGES[i](model)
sfc.finalize(model)
model.doc.saveAs(str(model.out/'SuperFamicom_Study.FCStd'))
