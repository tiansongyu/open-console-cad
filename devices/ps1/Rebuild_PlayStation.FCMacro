"""Rebuild the original SCPH-1000 console, controller and connection kit."""
from pathlib import Path
import sys,importlib
root=Path(__file__).resolve().parent;repo=root.parents[1]
if str(repo/'tools') not in sys.path:sys.path.insert(0,str(repo/'tools'))
from cadlib import core,geometry,ps1
for module in [geometry,core,ps1]:importlib.reload(module)
model=core.Study(repo,'ps1');model.out=root/'output/rebuilt'
for folder in ['iterations','reports','previews','drawings']:(model.out/folder).mkdir(parents=True,exist_ok=True)
for stage in sorted(ps1.STAGES):ps1.STAGES[stage](model)
ps1.finalize(model)
