"""Rebuild the Nintendo 64 study from all available source stages."""
from pathlib import Path
import sys,importlib
root=Path(__file__).resolve().parent;repo=root.parents[1]
if str(repo/'tools') not in sys.path:sys.path.insert(0,str(repo/'tools'))
from cadlib import core,geometry,retro_common,n64,deliver
for module in [geometry,core,retro_common,n64,deliver]:importlib.reload(module)
model=core.Study(repo,'n64');model.out=root/'output/rebuilt'
for folder in ['iterations','reports','previews','drawings']:(model.out/folder).mkdir(parents=True,exist_ok=True)
for stage in sorted(n64.STAGES):n64.STAGES[stage](model)
deliver.finalize(model)
