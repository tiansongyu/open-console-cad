"""Rebuild the original WiiU collection through all source stages."""
from pathlib import Path
import sys,importlib
root=Path(__file__).resolve().parent;repo=root.parents[1]
if str(repo/'tools') not in sys.path:sys.path.insert(0,str(repo/'tools'))
from cadlib import core,geometry,retro_common,fidelity_wiiu,wiiu,deliver
for module in [geometry,core,retro_common,fidelity_wiiu,wiiu,deliver]:importlib.reload(module)
model=core.Study(repo,'wiiu');model.out=root/'output/rebuilt'
for folder in ['iterations','reports','previews','drawings']:(model.out/folder).mkdir(parents=True,exist_ok=True)
for stage in wiiu.STAGES:stage(model)
wiiu.finalize(model)
