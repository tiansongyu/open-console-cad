"""Rebuild original 2001 Xbox and Duke from all staged source."""
from pathlib import Path
import sys,importlib
root=Path(__file__).resolve().parent;repo=root.parents[1]
sys.path.insert(0,str(repo/'tools'))
from cadlib import core,xbox,deliver
importlib.reload(xbox)
model=core.Study(repo,'xbox');model.out=root/'output/rebuilt'
for folder in ['iterations','reports','previews','drawings']:(model.out/folder).mkdir(parents=True,exist_ok=True)
for i in sorted(xbox.STAGES):xbox.STAGES[i](model)
xbox.finalize(model)
model.doc.saveAs(str(model.out/'OriginalXbox_Study.FCStd'))
