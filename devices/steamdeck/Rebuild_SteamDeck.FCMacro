"""Rebuild the 2022 LCD Steam Deck study without overwriting its delivered models."""
from pathlib import Path
import sys,importlib
root=Path(__file__).resolve().parent;repo=root.parents[1]
if str(repo/'tools') not in sys.path:sys.path.insert(0,str(repo/'tools'))
from cadlib import core,geometry,fidelity_steamdeck,steamdeck,deliver
for module in [geometry,core,fidelity_steamdeck,steamdeck,deliver]:importlib.reload(module)
model=core.Study(repo,'steamdeck');model.out=root/'output/rebuilt'
for folder in ['iterations','reports','previews','drawings']:(model.out/folder).mkdir(parents=True,exist_ok=True)
for stage in sorted(steamdeck.STAGES):steamdeck.STAGES[stage](model)
deliver.finalize(model)
