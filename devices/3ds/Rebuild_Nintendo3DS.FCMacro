"""Rebuild the original 3DS into output/rebuilt without replacing the delivery."""
from pathlib import Path
import sys,importlib
root=Path(__file__).resolve().parent;repo=root.parents[1]
if str(repo/'tools') not in sys.path:sys.path.insert(0,str(repo/'tools'))
from cadlib import core,geometry,handheld_refinement,fidelity_3ds,clamshell,deliver
for module in [geometry,core,handheld_refinement,fidelity_3ds,clamshell,deliver]:importlib.reload(module)
model=core.Study(repo,'3ds');model.out=root/'output/rebuilt'
for folder in ['iterations','reports','previews','drawings']:(model.out/folder).mkdir(parents=True,exist_ok=True)
for stage in range(1,16):clamshell.STAGES[stage](model)
deliver.finalize(model)
