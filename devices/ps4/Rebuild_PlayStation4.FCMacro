"""Rebuild the original CUH-1000A console, DualShock 4 and connection kit."""
from pathlib import Path
import sys,importlib
root=Path(__file__).resolve().parent;repo=root.parents[1]
if str(repo/'tools') not in sys.path:sys.path.insert(0,str(repo/'tools'))
from cadlib import core,geometry,ps4
for module in [geometry,core,ps4]:importlib.reload(module)
model=core.Study(repo,'ps4');model.out=root/'output/rebuilt'
for folder in ['iterations','reports','previews','drawings']:(model.out/folder).mkdir(parents=True,exist_ok=True)
for stage in sorted(ps4.STAGES):ps4.STAGES[stage](model)
ps4.finalize(model)
